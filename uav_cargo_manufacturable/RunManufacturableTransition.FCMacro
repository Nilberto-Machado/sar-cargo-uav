"""Collision-free transition with stopped/locked rotors and mirrored tilt directions."""

import FreeCAD as App
import FreeCADGui as Gui
from PySide import QtCore

DOC = "CargoUAV_HybridVTOL_Manufacturable"
CG = App.Vector(1350, 0, 0)
DT, TOTAL = 0.04, 20.0


def smooth(x):
    x = max(0.0, min(1.0, x))
    return x * x * (3 - 2 * x)


def mix(a, b, s):
    return a + (b - a) * s


class Animator(QtCore.QObject):
    def __init__(self, doc):
        super().__init__()
        self.doc = doc
        self.body = doc.getObject("AircraftAssembly")
        self.state = doc.getObject("AnimationState")
        for name, ptype in (("RotorLock", "App::PropertyString"),
                            ("TiltPermission", "App::PropertyBool"),
                            ("FrontTilt", "App::PropertyAngle"),
                            ("RearTilt", "App::PropertyAngle")):
            if name not in self.state.PropertiesList:
                self.state.addProperty(ptype, name, "Safety interlock")
        self.codes = ("FL", "FR", "RL", "RR")
        self.pods = [doc.getObject("TiltPod_" + c) for c in self.codes]
        self.rotors = [doc.getObject("Rotor_" + c) for c in self.codes]
        self.pusher = doc.getObject("Rotor_Pusher")
        self.signs = (1, -1, -1, 1)
        self.angles = [0.0] * 4
        self.index_start = None
        self.pusher_angle = 0.0
        self.t = 0.0
        self.timer = QtCore.QTimer()
        self.timer.timeout.connect(self.tick)
        self.timer.start(int(DT * 1000))

    def command(self, t):
        if t < 2:
            s = smooth(t / 2)
            return "VTOL spin-up", 0, 0, 0, 0, int(mix(0, 1600, s)), 0, "UNLOCKED", False
        if t < 6:
            s = smooth((t - 2) / 4)
            return "Vertical takeoff", 0, mix(0, 1500, s), 0, 0, 1600, 0, "UNLOCKED", False
        if t < 9:
            s = smooth((t - 6) / 3)
            return "Pusher start; pods remain vertical", mix(0, -500, s), mix(1500, 1650, s), mix(0, -3, s), 0, 1600, int(mix(0, 5200, s)), "UNLOCKED", False
        if t < 11:
            s = smooth((t - 9) / 2)
            return "Wing loading; VTOL braking", mix(-500, -1200, s), mix(1650, 1750, s), mix(-3, -6, s), 0, int(mix(1600, 0, s)), int(mix(5200, 6200, s)), "BRAKING", False
        if t < 12:
            s = smooth(t - 11)
            return "Stopped rotor indexing", mix(-1200, -1350, s), 1750, -6, 0, 0, 6200, "INDEXING", False
        if t < 14:
            s = smooth((t - 12) / 2)
            return "Locked mirrored tilt", mix(-1350, -1700, s), 1750, mix(-6, -3, s), mix(0, 90, s), 0, int(mix(6200, 6500, s)), "LOCKED", True
        s = smooth((t - 14) / 6)
        return "Cruise", mix(-1700, -3100, s), 1750, mix(-3, 0, min(1, 2 * s)), 90, 0, 6500, "LOCKED", True

    def tick(self):
        self.t += DT * max(0.05, float(self.state.AnimationSpeed))
        if self.t > TOTAL:
            if self.state.Loop:
                self.t, self.angles, self.index_start, self.pusher_angle = 0.0, [0.0] * 4, None, 0.0
            else:
                self.stop()
                return
        phase, dx, dz, pitch, tilt_mag, vtol_rpm, pusher_rpm, lock, permit = self.command(self.t)
        body_rot = App.Rotation(App.Vector(0, 1, 0), pitch)
        self.body.Placement = App.Placement(App.Vector(dx, 0, dz) + CG - body_rot.multVec(CG), body_rot)

        permitted = vtol_rpm == 0 and lock == "LOCKED" and permit
        front_tilt = -tilt_mag if permitted else 0.0
        rear_tilt = tilt_mag if permitted else 0.0
        for code, pod in zip(self.codes, self.pods):
            pod.Placement.Rotation = App.Rotation(App.Vector(0, 1, 0), rear_tilt if code.startswith("R") else front_tilt)

        if self.t < 11:
            vis = min(vtol_rpm, 320)
            for i, rotor in enumerate(self.rotors):
                self.angles[i] = (self.angles[i] + self.signs[i] * vis * 6 * DT) % 360
                rotor.Placement.Rotation = App.Rotation(App.Vector(0, 0, 1), self.angles[i])
        elif self.t < 12:
            if self.index_start is None:
                self.index_start = list(self.angles)
            s = smooth(self.t - 11)
            for i, rotor in enumerate(self.rotors):
                start = self.index_start[i]
                target = 90 + 360 * round((start - 90) / 360)
                self.angles[i] = mix(start, target, s)
                rotor.Placement.Rotation = App.Rotation(App.Vector(0, 0, 1), self.angles[i])
        else:
            for i, rotor in enumerate(self.rotors):
                self.angles[i] = 90
                rotor.Placement.Rotation = App.Rotation(App.Vector(0, 0, 1), 90)

        self.pusher_angle = (self.pusher_angle + min(pusher_rpm, 360) * 6 * DT) % 360
        self.pusher.Placement.Rotation = App.Rotation(App.Vector(1, 0, 0), self.pusher_angle)
        self.state.SimulationTime, self.state.Phase = self.t, phase
        self.state.Altitude, self.state.Pitch = dz, pitch
        self.state.TiltAngle = front_tilt
        self.state.FrontTilt, self.state.RearTilt = front_tilt, rear_tilt
        self.state.VTOL_RPM, self.state.Pusher_RPM = int(vtol_rpm), int(pusher_rpm)
        self.state.RotorLock, self.state.TiltPermission = lock, permit
        self.doc.recompute()
        Gui.activeDocument().activeView().redraw()

    def stop(self):
        self.timer.stop()
        self.state.Phase = "Stopped"
        self.doc.recompute()


doc = App.ActiveDocument
if doc is None or doc.Name != DOC:
    raise RuntimeError("Open CargoUAV_HybridVTOL_Manufacturable.FCStd first")
for attr in ("VTailTiltAnimator", "SafeTransitionAnimator", "ManufacturableAnimator"):
    old = getattr(App, attr, None)
    if old is not None:
        try:
            old.stop()
        except Exception:
            pass
Gui.activeDocument().activeView().viewAxonometric()
Gui.activeDocument().activeView().fitAll()
App.ManufacturableAnimator = Animator(doc)
