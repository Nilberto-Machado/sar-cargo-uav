"""Animate V-tail hybrid VTOL takeoff, nacelle tilt, pusher start and cruise."""

import FreeCAD as App
import FreeCADGui as Gui
from PySide import QtCore

DOC = "CargoUAV_HybridVTOL_VTail_TiltRotor_Animated"
CG = App.Vector(1350, 0, 0)
DT = 0.04
TOTAL = 17.0


def smooth(x):
    x = max(0.0, min(1.0, x))
    return x * x * (3 - 2 * x)


def mix(a, b, s):
    return a + (b - a) * s


class Animator(QtCore.QObject):
    def __init__(self, doc):
        super().__init__()
        self.doc = doc
        self.body = doc.getObject("AircraftAssembly")
        self.state = doc.getObject("AnimationState")
        self.tilts = [doc.getObject("TiltPod_" + c) for c in ("FL", "FR", "RL", "RR")]
        self.rotors = [doc.getObject("Rotor_" + c) for c in ("FL", "FR", "RL", "RR")]
        self.pusher = doc.getObject("Rotor_Pusher")
        self.signs = (1, -1, -1, 1)
        self.angles = [0.0] * 4
        self.pusher_angle = 0.0
        self.t = 0.0
        self.timer = QtCore.QTimer()
        self.timer.timeout.connect(self.tick)
        self.timer.start(int(DT * 1000))

    def state_at(self, t):
        if t < 2:
            s = smooth(t / 2)
            return "VTOL spin-up", 0, 0, 0, 0, int(mix(0, 1600, s)), 0
        if t < 6:
            s = smooth((t - 2) / 4)
            return "Vertical takeoff", 0, mix(0, 1500, s), 0, 0, 1600, 0
        if t < 11:
            s = smooth((t - 6) / 5)
            return (
                "Transition: nacelles tilt as gasoline pusher starts",
                mix(0, -1300, s), mix(1500, 1750, s), mix(0, -6, s),
                mix(0, -90, s), int(mix(1600, 0, s)), int(mix(0, 6000, s)),
            )
        s = smooth((t - 11) / 6)
        return (
            "Cruise: nacelles aligned and pusher active",
            mix(-1300, -2900, s), 1750, mix(-6, 0, min(1, 2 * s)),
            -90, 0, 6500,
        )

    def tick(self):
        self.t += DT * max(0.05, float(self.state.AnimationSpeed))
        if self.t > TOTAL:
            if self.state.Loop:
                self.t = 0
                self.angles = [0.0] * 4
                self.pusher_angle = 0
            else:
                self.stop()
                return
        phase, dx, dz, pitch, tilt_angle, vtol_rpm, pusher_rpm = self.state_at(self.t)
        body_rot = App.Rotation(App.Vector(0, 1, 0), pitch)
        self.body.Placement = App.Placement(App.Vector(dx, 0, dz) + CG - body_rot.multVec(CG), body_rot)

        for pod in self.tilts:
            pod.Placement.Rotation = App.Rotation(App.Vector(0, 1, 0), tilt_angle)

        visual_rpm = min(vtol_rpm, 320)
        for i, rotor in enumerate(self.rotors):
            if vtol_rpm == 0:
                self.angles[i] = 0
            else:
                self.angles[i] = (self.angles[i] + self.signs[i] * visual_rpm * 6 * DT) % 360
            rotor.Placement.Rotation = App.Rotation(App.Vector(0, 0, 1), self.angles[i])

        self.pusher_angle = (self.pusher_angle + min(pusher_rpm, 360) * 6 * DT) % 360
        self.pusher.Placement.Rotation = App.Rotation(App.Vector(1, 0, 0), self.pusher_angle)

        self.state.SimulationTime = self.t
        self.state.Phase = phase
        self.state.Altitude = dz
        self.state.Pitch = pitch
        self.state.TiltAngle = tilt_angle
        self.state.VTOL_RPM = int(vtol_rpm)
        self.state.Pusher_RPM = int(pusher_rpm)
        self.doc.recompute()
        Gui.activeDocument().activeView().redraw()

    def stop(self):
        self.timer.stop()
        self.state.Phase = "Stopped"
        self.doc.recompute()


doc = App.ActiveDocument
if doc is None or doc.Name != DOC:
    raise RuntimeError("Open CargoUAV_HybridVTOL_VTail_TiltRotor_Animated.FCStd first")
old = getattr(App, "VTailTiltAnimator", None)
if old is not None:
    try:
        old.stop()
    except Exception:
        pass
Gui.activeDocument().activeView().viewAxonometric()
Gui.activeDocument().activeView().fitAll()
App.VTailTiltAnimator = Animator(doc)
